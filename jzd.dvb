Attribute VB_Name = "模块1"
Sub jzd()
    Dim xlapp As Excel.Application
    Dim xlbook As Excel.Workbook
    Set xlbook = xlapp.Workbooks.Add
    Dim xlsheet As Excel.Sheets
    Set xlsheet = xlbook.Worksheets("sheet1")
    
    
    
    
    
End Sub
